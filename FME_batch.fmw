FME workspace FME_batch.fmw
Title: Run a batch file
Description: This example shows how to run a batch file from inside of FME using the SystemCaller transformer.
Usage: Save the workspace.
    The workspace will have an associated directory.
    Locate the mkdir_test.bat file and copy it to c:\temp.
    Run the workspace - it will create the directory c:\temp\test 
    Change the SystemCaller transformer to use the command 'mkdir d:\test'
    Run the workspace - the workspace will show an error.
History: 2012-10-16,Aaron Koning,Created

Parameters:
- anaconda_loc = C:\Users\Derek\Anaconda3   # Where is anaconda3 stored?
- polygon_file_location = data/geodatabase/OMS_NHM_20201223.gdb   # Select shapefile in data/polygon_input/
- identifier_column_name = KRCode   # What is the ID column name of the shapefile?
- lcheck_factor = 0.3   # OPTIONAL, hoe strict checken?
- squareness_factor = 0.7   # OPTIONAL, hoe snel zijn polygonen vierkant?
- lf_factor = 2.5   # OPTIONAL, welke hoogte/breedte verhouding telt als langwerpig?
- cl_distance = 1.0   # OPTIONAL, simplification for centerline calculation
- layer = vWaterafvoer   # Welke laag wil je inladen?

Creator
    GEOMTYPE = Geometry Object
    NUM = 1
    CREATED -> SystemCaller
Note: .\workflow.bat $(anaconda_loc) $(polygon_file_location) $(identifier_column_name) / OPTIONAL: $(lcheck_factor) $(squareness_factor) $(lf_factor) $(cl_distance) / # anaconda3_location=C:\Users\Derek\Anaconda3 , location to check for conda environment / # polygon_file_location=data/polygon_input/shapefile.sh, shapefile location / # identifier_column_name=KRcode, object id column name / OPTIONAL parameters / # lcheck_factor = 0.3, Een hogere lcheck betekent dat er meer gecheckt moet worden. / # squareness_factor = 0.7, Een hogere squareness betekent dat minder langwerpige polygonen eerder als vierkant worden bestempelt. Hierdoor wordt dan de lengte van de polygoon met de oppervlaktemethode berekent. / # lf = 2.5, Verhouding waarop polygonen als langwerpig worden beschouwd. Een hogere lf leidt tot minder als langwerpig beschouwde polygonen. / # distance = 1, Simplificatiefactor voor centerlijn. Hogere waardes leidt tot verwdijnen van dunne polygonen.
Note: runs workflow.bat
Note: output in output/output.xlsx
SystemCaller
    ATTR = _exit_code
    CMD = .\workflow.bat $(anaconda_loc) $(polygon_file_location) $(identifier_column_name) $(layer) $(lcheck_factor) $(squareness_factor) $(lf_factor) $(cl_distance)
